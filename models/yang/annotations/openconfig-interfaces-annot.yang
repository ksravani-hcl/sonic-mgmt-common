module openconfig-interfaces-annot {

    yang-version "1";

    namespace "http://openconfig.net/yang/annotation/openconfig-interfaces-annot";
    prefix "oc-interfaces-annot";

    import sonic-extensions { prefix sonic-ext; }
    import openconfig-interfaces { prefix oc-intf; }
    import openconfig-vlan {prefix oc-vlan; }
    import openconfig-if-ip {prefix oc-ip; }
    import openconfig-if-aggregate { prefix oc-lag; }
    import openconfig-p4rt { prefix "p4rt-if"; }
    import openconfig-platform-port { prefix "oc-plat-port"; }
    import openconfig-platform-transceiver { prefix "oc-plat-xcvr"; }

    deviation /oc-intf:interfaces/oc-intf:interface {
        deviate add {
            sonic-ext:key-transformer "intf_tbl_key_xfmr";
            sonic-ext:table-transformer "intf_table_xfmr";
        }
    }

    deviation /oc-intf:interfaces/oc-intf:interface/oc-intf:config/oc-intf:name {
        deviate add {
            sonic-ext:field-transformer "intf_name_xfmr";
        }
    }

    deviation /oc-intf:interfaces/oc-intf:interface/oc-eth:ethernet/oc-eth:config {
        deviate add {
            sonic-ext:subtree-transformer "intf_eth_port_config_xfmr";
            sonic-ext:path-transformer "intf_eth_port_config_path_xfmr";
        }
    }

    deviation /oc-intf:interfaces/oc-intf:interface/oc-eth:ethernet/oc-eth:state {
        deviate add {
            sonic-ext:db-name "APPL_DB";
        }
    }

    deviation /oc-intf:interfaces/oc-intf:interface/oc-eth:ethernet/oc-eth:state/oc-eth:auto-negotiate {
        deviate add {
            sonic-ext:field-transformer "intf_eth_auto_neg_xfmr";
            sonic-ext:field-name "autoneg";
        }
    }
    
    deviation /oc-intf:interfaces/oc-intf:interface/oc-eth:ethernet/oc-eth:state/oc-eth:port-speed {
        deviate add {
            sonic-ext:field-transformer "intf_eth_port_speed_xfmr";
            sonic-ext:field-name "speed";
        }
    }

    deviation /oc-intf:interfaces/oc-intf:interface/oc-eth:ethernet/oc-eth:state/oc-lag:aggregate-id {
        deviate add {
            sonic-ext:field-transformer "intf_eth_aggr_id_xfmr";
        }
    }

    deviation /oc-intf:interfaces/oc-intf:interface/oc-intf:state {
        deviate add {
            sonic-ext:db-name "APPL_DB";
        }
    }

    deviation /oc-intf:interfaces/oc-intf:interface/oc-intf:config/oc-intf:mtu {
        deviate add {
            sonic-ext:field-transformer "intf_mtu_xfmr";
        }
    }


    deviation /oc-intf:interfaces/oc-intf:interface/oc-intf:state/oc-intf:admin-status {
        deviate add {
            sonic-ext:field-transformer "intf_admin_status_xfmr";
            sonic-ext:field-name "admin_status";
        }
    }

    deviation /oc-intf:interfaces/oc-intf:interface/oc-intf:config/oc-intf:enabled {
        deviate add {
            sonic-ext:field-transformer "intf_enabled_xfmr";
            sonic-ext:field-name "admin_status";
        }
    }

    deviation /oc-intf:interfaces/oc-intf:interface/oc-lag:aggregation/oc-lag:config/oc-lag:min-links {
        deviate add {
            sonic-ext:field-transformer "lag_min_links_xfmr";
            sonic-ext:field-name "min_links";
        }
    }

    deviation /oc-intf:interfaces/oc-intf:interface/oc-lag:aggregation/oc-lag:state {
      deviate add {
            sonic-ext:subtree-transformer "intf_lag_state_xfmr";
            sonic-ext:path-transformer "intf_lag_state_path_xfmr";
      }
    }

    deviation /oc-intf:interfaces/oc-intf:interface/oc-intf:state/oc-intf:name {
        deviate add {
            sonic-ext:field-transformer "intf_name_xfmr";
        }
    }

    deviation /oc-intf:interfaces/oc-intf:interface/oc-intf:state/oc-intf:enabled {
        deviate add {
            sonic-ext:field-transformer "intf_enabled_xfmr";
            sonic-ext:field-name "admin_status";
        }
    }

    deviation /oc-intf:interfaces/oc-intf:interface/oc-intf:state/oc-intf:counters {
        deviate add {
            sonic-ext:subtree-transformer "intf_get_counters_xfmr";
            sonic-ext:db-name "COUNTERS_DB";
            sonic-ext:subscribe-on-change "disable";
        }
    }

    deviation /oc-intf:interfaces/oc-intf:interface/oc-eth:ethernet/oc-eth:state/oc-eth:counters {
        deviate add {
            sonic-ext:db-name "COUNTERS_DB";
            sonic-ext:subtree-transformer "intf_get_ether_counters_xfmr";
            sonic-ext:subscribe-on-change "disable";
        }
    }

    deviation /oc-intf:interfaces/oc-intf:interface/oc-lag:aggregation/oc-vlan:switched-vlan {
        deviate add {
            sonic-ext:subtree-transformer "sw_vlans_xfmr";
            sonic-ext:path-transformer "sw_vlans_path_xfmr";
        }
    }

     deviation /oc-intf:interfaces/oc-intf:interface/oc-eth:ethernet/oc-vlan:switched-vlan {
        deviate add {
            sonic-ext:subtree-transformer "sw_vlans_xfmr";
            sonic-ext:path-transformer "sw_vlans_path_xfmr";
        }
    }
    
    deviation /oc-intf:interfaces {
      deviate add {
        sonic-ext:pre-transformer "intf_pre_xfmr";
        sonic-ext:post-transformer "intf_post_xfmr";
      }
    }
    
    deviation /oc-intf:interfaces/oc-intf:interface/oc-intf:subinterfaces {
        deviate add {
            sonic-ext:table-name "NONE";
        }
    }
    
    deviation /oc-intf:interfaces/oc-intf:interface/oc-intf:subinterfaces/oc-intf:subinterface {
        deviate add {
            sonic-ext:table-transformer "intf_subintfs_table_xfmr";
            sonic-ext:virtual-table "true";
            sonic-ext:key-transformer "intf_subintfs_xfmr";
            sonic-ext:path-transformer "intf_ip_path_xfmr";
        }
    }
    
    deviation /oc-intf:interfaces/oc-intf:interface/oc-intf:subinterfaces/oc-intf:subinterface/oc-intf:config/oc-intf:index {
        deviate add {
            sonic-ext:field-transformer "subif_index_xfmr";
        }
    }
    
    deviation /oc-intf:interfaces/oc-intf:interface/oc-intf:subinterfaces/oc-intf:subinterface/oc-intf:state/oc-intf:index {
        deviate add {
            sonic-ext:field-transformer "subif_index_xfmr";
        }
    }
    
    deviation /oc-intf:interfaces/oc-intf:interface/oc-intf:subinterfaces/oc-intf:subinterface/oc-ip:ipv4/oc-ip:addresses {
        deviate add {
            sonic-ext:table-name "NONE";
            sonic-ext:subtree-transformer "intf_ip_addr_xfmr";
        }
    }
    
    deviation /oc-intf:interfaces/oc-intf:interface/oc-intf:subinterfaces/oc-intf:subinterface/oc-ip:ipv6/oc-ip:addresses {
        deviate add {
            sonic-ext:table-name "NONE";
            sonic-ext:subtree-transformer "intf_ip_addr_xfmr";
        }
    }

    deviation /oc-intf:interfaces/oc-intf:interface/oc-intf:subinterfaces/oc-intf:subinterface/oc-ip:ipv4/oc-ip:addresses/oc-ip:address {
        deviate add {
            sonic-ext:key-transformer "subintf_ip_addr_key_xfmr";
        }
    }

    deviation /oc-intf:interfaces/oc-intf:interface/oc-intf:subinterfaces/oc-intf:subinterface/oc-ip:ipv6/oc-ip:addresses/oc-ip:address {
        deviate add {
            sonic-ext:key-transformer "subintf_ip_addr_key_xfmr";
        }
    }
    deviation /oc-intf:interfaces/oc-intf:interface/oc-intf:subinterfaces/oc-intf:subinterface/oc-ip:ipv4 {
        deviate add {
            sonic-ext:table-transformer "intf_table_xfmr";
        }
    }

    deviation /oc-intf:interfaces/oc-intf:interface/oc-intf:subinterfaces/oc-intf:subinterface/oc-ip:ipv6 {
        deviate add {
            sonic-ext:key-transformer "subintf_ipv6_tbl_key_xfmr";
            sonic-ext:table-transformer "intf_table_xfmr";
        }
    }
    
    deviation /oc-intf:interfaces/oc-intf:interface/oc-intf:subinterfaces/oc-intf:subinterface/oc-ip:ipv6/oc-ip:config/oc-ip:enabled {
        deviate add {
            sonic-ext:field-transformer "ipv6_enabled_xfmr";
        }
    }

    deviation /oc-intf:interfaces/oc-intf:interface/oc-intf:subinterfaces/oc-intf:subinterface/oc-ip:ipv6/oc-ip:state/oc-ip:enabled {
        deviate add {
            sonic-ext:field-transformer "ipv6_enabled_xfmr";
        }
    }

    deviation /oc-intf:interfaces/oc-intf:interface/oc-vlan:routed-vlan {
        deviate add {
	    sonic-ext:path-transformer "intf_ip_path_xfmr";
        }
    }

    deviation /oc-intf:interfaces/oc-intf:interface/oc-vlan:routed-vlan/oc-vlan:config/oc-vlan:vlan {
        deviate add {
             sonic-ext:field-transformer "intf_routed_vlan_name_xfmr";
        }
    }

    deviation /oc-intf:interfaces/oc-intf:interface/oc-vlan:routed-vlan/oc-vlan:state/oc-vlan:vlan {
        deviate add {
            sonic-ext:field-transformer "intf_routed_vlan_name_xfmr";
        }
    }

    deviation /oc-intf:interfaces/oc-intf:interface/oc-vlan:routed-vlan/oc-ip:ipv4/oc-ip:addresses {
        deviate add {
            sonic-ext:table-name "NONE";
            sonic-ext:subtree-transformer "routed_vlan_ip_addr_xfmr";
        }
    }

    deviation /oc-intf:interfaces/oc-intf:interface/oc-vlan:routed-vlan/oc-ip:ipv6/oc-ip:addresses {
        deviate add {
            sonic-ext:table-name "NONE";
            sonic-ext:subtree-transformer "routed_vlan_ip_addr_xfmr";
        }
    }

    deviation /oc-intf:interfaces/oc-intf:interface/oc-vlan:routed-vlan/oc-ip:ipv6/oc-ip:state {
        deviate add {
            sonic-ext:db-name "APPL_DB";
        }
    }

    deviation /oc-intf:interfaces/oc-intf:interface/oc-vlan:routed-vlan/oc-ip:ipv6/oc-ip:config/oc-ip:enabled {
        deviate add {
            sonic-ext:field-transformer "ipv6_enabled_xfmr";
            sonic-ext:field-name "ipv6_use_link_local_only";
        }
    }

    deviation /oc-intf:interfaces/oc-intf:interface/oc-vlan:routed-vlan/oc-ip:ipv6/oc-ip:state/oc-ip:enabled {
        deviate add {
            sonic-ext:field-transformer "ipv6_enabled_xfmr";
            sonic-ext:field-name "ipv6_use_link_local_only";
        }
    }

    deviation /oc-intf:interfaces/oc-intf:interface/oc-intf:config/p4rt-if:id {
        deviate add {
            sonic-ext:field-transformer "pins_if_id_xfmr";
        }
    }

    deviation /oc-intf:interfaces/oc-intf:interface/oc-intf:state/oc-intf:ifindex {
        deviate add {
            sonic-ext:field-transformer "pins_ifindex_xfmr";
            sonic-ext:table-name "P4RT_PORT_ID_TABLE";
        }
    }

    deviation /oc-intf:interfaces/oc-intf:interface/oc-intf:state/p4rt-if:id {
        deviate add {
            sonic-ext:field-transformer "pins_if_id_xfmr";
            sonic-ext:table-name "P4RT_PORT_ID_TABLE";
            sonic-ext:db-name "APPL_DB";
        }
    }

    deviation /oc-intf:interfaces/oc-intf:interface/oc-intf:state/oc-plat-port:hardware-port {
        deviate add {
            sonic-ext:field-transformer "intf_hardware_port_xfmr";
            sonic-ext:field-name "index";
        }
    }

    deviation /oc-intf:interfaces/oc-intf:interface/oc-intf:state/oc-plat-xcvr:transceiver {
        deviate add {
            sonic-ext:field-transformer "intf_transceiver_xfmr";
        }
    }

    deviation /oc-intf:interfaces/oc-intf:interface/oc-intf:state/oc-plat-xcvr:physical-channel {
        deviate add {
            sonic-ext:field-transformer "intf_physical_channel_xfmr";
        }
    }

    deviation /oc-intf:interfaces/oc-intf:interface/oc-intf:state/oc-intf:oper-status {
        deviate add {
            sonic-ext:field-transformer "intf_oper_status_xfmr";
            sonic-ext:composite-field-names "PORT_TABLE:oper_status,MGMT_PORT_TABLE:oper_status";
        }
    }

    deviation /oc-intf:interfaces/oc-intf:interface/oc-eth:ethernet/oc-eth:state/oc-eth:port-speed {
        deviate add {
            sonic-ext:field-transformer "intf_eth_port_speed_xfmr";
            sonic-ext:field-name "speed";
        }
    }

    deviation /oc-intf:interfaces/oc-intf:interface/oc-intf:config/oc-intf:enabled {
        deviate add {
            sonic-ext:field-transformer "intf_enabled_xfmr";
        }
    }

    deviation /oc-intf:interfaces/oc-intf:interface/oc-intf:state/oc-intf:enabled {
        deviate add {
            sonic-ext:field-transformer "intf_enabled_xfmr";
        }
    }

    deviation /oc-intf:interfaces/oc-intf:interface/oc-intf:config/oc-intf:mtu {
        deviate add {
            sonic-ext:field-transformer "intf_mtu_xfmr";
        }
    }

    deviation /oc-intf:interfaces/oc-intf:interface/oc-intf:state/oc-intf:mtu {
        deviate add {
            sonic-ext:field-transformer "intf_mtu_xfmr";
        }
    }

    deviation /oc-intf:interfaces/oc-intf:interface/oc-intf:state/oc-intf:management {
        deviate add {
            sonic-ext:field-transformer "intf_mgmt_xfmr";
        }
    }

    deviation /oc-intf:interfaces/oc-intf:interface/oc-intf:state/oc-intf:cpu {
        deviate add {
            sonic-ext:field-transformer "intf_cpu_xfmr";
        }
    }

    deviation /oc-intf:interfaces/oc-intf:interface/oc-intf:state/oc-intf:description {
        deviate add {
            sonic-ext:field-transformer "intf_description_xfmr";
        }
    }

    deviation /oc-intf:interfaces/oc-intf:interface/oc-eth:ethernet/oc-eth:state/oc-eth:mac-address {
        deviate add {
            sonic-ext:field-transformer "intf_eth_mac_address_xfmr";
        }
    }

    deviation /oc-intf:interfaces/oc-intf:interface/oc-intf:state/oc-intf:counters {
        deviate add {
            sonic-ext:subtree-transformer "intf_get_counters_xfmr";
            sonic-ext:db-name "COUNTERS_DB";
        }
    }

    deviation /oc-intf:interfaces/oc-intf:interface/oc-eth:ethernet/oc-eth:state/oc-eth:counters {
        deviate add {
            sonic-ext:db-name "COUNTERS_DB";
            sonic-ext:subtree-transformer "intf_get_ether_counters_xfmr";
        }
    }

    deviation /oc-intf:interfaces/oc-intf:interface/oc-intf:subinterfaces/oc-intf:subinterface/oc-ip:ipv4/oc-ip:state/oc-ip:counters {
        deviate add {
            sonic-ext:db-name "COUNTERS_DB";
            sonic-ext:subtree-transformer "intf_ipv4_counters_xfmr";
        }
    }

    deviation /oc-intf:interfaces/oc-intf:interface/oc-intf:subinterfaces/oc-intf:subinterface/oc-ip:ipv6/oc-ip:state/oc-ip:counters {
        deviate add {
            sonic-ext:db-name "COUNTERS_DB";
            sonic-ext:subtree-transformer "intf_ipv6_counters_xfmr";
        }
    }
}
